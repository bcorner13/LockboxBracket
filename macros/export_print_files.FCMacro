# -*- coding: utf-8 -*-
"""
export_print_files.FCMacro — Lockbox Bracket

Exports PRINTABLE geometry only: the bracket Body, never the Assembly or the
M3 screws.

Why this exists: the community macro 3D_Printer_3mf_Workflow.FCMacro exports
FreeCADGui.Selection. With the Assembly selected it happily meshes the twelve
M3x10 screws into the print file, which is useless to a slicer. This macro
pins the selection to the Body so that cannot happen.

Output (overwritten in place):
    stl/Lockbox Bracket.stl

It writes the STL only. 3mf/ holds SLICER PROJECTS (Creality Print), which carry
print settings this macro knows nothing about - it must not clobber them.

It also LEAVES THE BODY SELECTED, so you can immediately run the
3D_Printer_3mf_Workflow macro afterwards if you want its slicer-settings
round-trip - it will now pick up the bracket alone.

Idempotent. Does NOT save the document.

Run: Macro -> Macros... -> export_print_files -> Execute
"""

import os
import FreeCAD
import Mesh
import MeshPart

DOC_NAME = "Unnamed"
PROJECT = ("/Users/bradleycorner/Documents/3dPrinting/Commercial License/"
           "Lockbox Bracket")
BASENAME = "Lockbox Bracket"

# mesh quality - finer than FreeCAD's 0.1 default so the fillets stay smooth
LINEAR_DEFLECTION = 0.05
ANGULAR_DEFLECTION = 0.1745329252   # 10 degrees, in radians

doc = FreeCAD.getDocument(DOC_NAME)
body = doc.getObject("Body")

shape = body.Tip.Shape
if shape is None or shape.isNull():
    raise RuntimeError("Body.Tip has no shape - recompute the document first.")
if not shape.isValid():
    raise RuntimeError("Body.Tip shape is INVALID - fix the model before exporting.")
if len(shape.Solids) != 1:
    raise RuntimeError("Expected exactly 1 solid, found %d." % len(shape.Solids))

# ------------------------------------------------------------------ mesh it
mesh = MeshPart.meshFromShape(
    Shape=shape,
    LinearDeflection=LINEAR_DEFLECTION,
    AngularDeflection=ANGULAR_DEFLECTION,
    Relative=False,
)

tmp = doc.addObject("Mesh::Feature", "TempExportMesh")
tmp.Mesh = mesh

try:
    stl_path = os.path.join(PROJECT, "stl", BASENAME + ".stl")
    Mesh.export([tmp], stl_path)
finally:
    doc.removeObject(tmp.Name)

bb = mesh.BoundBox
print("exported printable geometry ONLY (no screws, no Assembly)")
print("  facets : %d" % mesh.CountFacets)
print("  bbox   : %.2f x %.2f x %.2f mm" % (bb.XLength, bb.YLength, bb.ZLength))
print("  z range: %.2f .. %.2f   (screws would push this past the flange top)"
      % (bb.ZMin, bb.ZMax))
print("  %8d bytes  %s" % (os.path.getsize(stl_path), os.path.basename(stl_path)))

# leave ONLY the Body selected, ready for the 3mf workflow macro
try:
    import FreeCADGui
    FreeCADGui.Selection.clearSelection()
    FreeCADGui.Selection.addSelection(doc.Name, body.Name)
    print("\nSelection pinned to Body - safe to run 3D_Printer_3mf_Workflow now.")
except Exception as exc:
    print("\n(could not set selection: %s)" % exc)
